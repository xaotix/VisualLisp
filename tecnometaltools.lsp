(defun c:extrair()
(setq pasta_etapa (strcat tm_com "2D_" arquivo ".tec\\DAT")) 
(if(=(vl-file-directory-p pasta_etapa) T)(DELFOLDER pasta_etapa))
(command "TEC_STDDEXTRACT3DINFO")
)
(defun delFolder (folder)
(vl-load-com)
(setq fso (vlax-create-object "Scripting.FileSystemObject"))
(vlax-invoke-method fso 'DeleteFolder folder  :vlax-false)
(vlax-release-object fso)
)
