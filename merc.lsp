(defun c:mercadorias ( / )
(SETQ executar "nada")
  (setq dcl_id (load_dialog "init.dcl"))
  (if (not (new_dialog "menus" dcl_id))
    (exit)
  )
(action_tile
    "cancel"						
    "(done_dialog) (prompt \"cancelado\")(princ)"		
    );action_tile
  (action_tile "Cancelar" "(done_dialog) (setq executar \"nada\")")
  (action_tile "sobre" "(mensagem_sobre)")
  (action_tile "2dmercadorias" "(done_dialog) (setq executar \"mercadorias\")")
  (action_tile "2dmateriais" "(done_dialog) (setq executar \"materiais\")")
  (action_tile "2dtratamentos" "(done_dialog) (setq executar \"tratamentos\")")  
  (action_tile "tmerc" "(done_dialog) (setq executar \"tmerc\")")  
  (action_tile "ftelha" "(done_dialog) (setq executar \"ftelha\")")  
  (action_tile "3dmercadorias" "(done_dialog) (setq executar \"3Dmercadorias\")")
  (action_tile "3dmateriais" "(done_dialog) (setq executar \"3Dmateriais\")")
  (action_tile "3dtratamentos" "(done_dialog) (setq executar \"3Dtratamentos\")")
  (start_dialog)
  (unload_dialog dcl_id)
    (EXECUTOR23)
	  (princ)
)

(defun EXECUTOR23 ()
(if (= executar "mercadorias")(c:mercadorias2))
(if (= executar "tmerc")(c:tmerc))
(if (= executar "materiais")(c:materiais))
(if (= executar "tratamentos")(c:tratamentos))
(if (= executar "ftelha")(c:ftelha))
(if (= executar "3Dmercadorias")(c:3dmercadorias))
(if (= executar "3Dmateriais")(c:3dmateriais))
(if (= executar "3Dtratamentos")(c:3dtratamentos))
(if (= executar "gerarpdf")(c:plot_pdf))
(if (= executar "marcacao")(c:merc))
(if (= executar "pdfprancha")(c:gerar_pdf_s2))
(if (= executar "pdfcfg")(c:CFG_PLOT_PDF))
(if (= executar "extrair3d")(c:extrair))
(if (= executar "gerar_dwt")(c:gerar_dwt))
(if (= executar "instalador")(c:valida_utilidades))
(if (= executar "scripts")(c:abrir_scripts))
)
(defun c:merc()
(c:mercadorias))



(defun c:ferramentas ( / )
(SETQ executar "nada")
  (setq dcl_id (load_dialog "init.dcl"))
  (if (not (new_dialog "menus2" dcl_id))
    (exit)
  )
(action_tile
    "cancel"						
    "(done_dialog) (prompt \"cancelado\")(princ)"		
    );action_tile
  (action_tile "Cancelar" "(done_dialog) (setq executar \"nada\")")
  (action_tile "sobre" "(mensagem_sobre)")
  (action_tile "gerarpdf" "(done_dialog) (setq executar \"gerarpdf\")")
  (action_tile "marcacao" "(done_dialog) (setq executar \"marcacao\")")
  (action_tile "gerar_dwt" "(done_dialog) (setq executar \"gerar_dwt\")")  
  (action_tile "ftelha" "(done_dialog) (setq executar \"ftelha\")")  
  (action_tile "pdfprancha" "(done_dialog) (setq executar \"pdfprancha\")")  
  (action_tile "scripts" "(done_dialog) (setq executar \"scripts\")")  
  (action_tile "extrair3d" "(done_dialog) (setq executar \"extrair3d\")")  
  (action_tile "instalador" "(done_dialog) (setq executar \"instalador\")") 
  (action_tile "pdfcfg" "(done_dialog) (setq executar \"pdfcfg\")")  
  (start_dialog)
  (unload_dialog dcl_id)
      (EXECUTOR23)
	  (princ)
)
(defun c:abrir_scripts()(command "START" "explorer C:\\Temp\\"))
